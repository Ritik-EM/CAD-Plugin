'
' Atlas CATIA V5 startup macro.
'
' Drop into %CATCustom%\CATStartup\ (or load via Tools > Macro > Macros).
' The COM ProgID "AtlasCadPlugin.Catia.CatiaAddin" is set by the
' [ClassInterface] attribute on CatiaAddin.cs; regasm.exe writes the
' HKCR mapping when the DLL is installed.
'
' The addin shows a mouse-clickable action menu (ActionMenuForm) — one
' button per action. Pick actions with the mouse; Close to exit.
'
Language="VBSCRIPT"

Dim atlas
Set atlas = CreateObject("AtlasCadPlugin.Catia.CatiaAddin")
atlas.Initialize(CATIA)
atlas.ShowMenu()
